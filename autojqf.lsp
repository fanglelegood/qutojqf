(command "GATTE" "b" "ZwmFrameMain_中文图纸标题栏" "图样代号" "HS41045.22.02.04" "Y")(command "GATTE" "b" "ZwmFrameMain_图样代号" "图样代号" "HS41045.22.02.04" "Y")(command "GATTE" "b" "ZwmFrameMain_中文图纸标题栏" "图样名称" "第二级末导叶根" "Y")(command "GATTE" "b" "末叶根12.5-54.7" "MH" "15.03" "Y")(command "GATTE" "b" "末叶根12.5-54.7" "HGJ" "25±0.2" "Y")(command "GATTE" "b" "末叶根12.5-54.7" "AG" "12.8" "Y")(command "GATTE" "b" "末叶根12.5-54.7" "HG1" "17.5" "Y")(command "GATTE" "b" "末叶根12.5-54.7" "HG2" "17.5" "Y")(command "GATTE" "b" "末叶根12.5-54.7" "HG" "25±0.2" "Y")(command "GATTE" "b" "末叶根12.5-54.7" "A" "16" "Y")(command "GATTE" "b" "末叶根12.5-54.7" "ALE" "13.5" "Y")(command "GATTE" "b" "末叶根12.5-54.7" "AB" "1" "Y")(command "GATTE" "b" "末叶根12.5-54.7" "RG1" "R2" "Y")(command "GATTE" "b" "末叶根12.5-54.7" "RG2" "R2" "Y")(command "GATTE" "b" "末叶根12.5-54.7" "RG3" "R1" "Y")(command "GATTE" "b" "末叶根12.5-54.7" "Δ" "89.69±0.15°" "Y")(command "GATTE" "b" "末叶根12.5-54.7" "HG3" "6.09" "Y")(command "GATTE" "b" "末叶根12.5-54.7" "HG4" "9.06" "Y")(command "GATTE" "b" "末叶根12.5-54.7" "菱形角" "20°" "Y")(command "GATTE" "b" "末叶根12.5-54.7" "B" "9.31" "Y")
(command "._close" "N")
